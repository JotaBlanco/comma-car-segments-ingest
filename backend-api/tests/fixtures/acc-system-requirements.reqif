# ACC System Requirements Specification
Generated from Reqs/requirements/*.yaml. Figures travel as external objects in the .reqifz archive under figures/. SPEC-RELATIONS is declared empty; the SRT-VERIFIES relation type exists so test cases can be linked in a later phase without a type-model change.

# Specification: ACC System Requirements Specification
- Document revision: 1.0
- Document status: Draft

## R1: Scope (Document section)
This document specifies the system-layer requirements for an Adaptive Cruise Control (ACC) system for a passenger car. The system is of FSRA type (full speed range adaptive cruise control) as classified by ISO 15622:2018 cl. 5.1 Table 1: it has no manual clutch dependency, it operates down to standstill, it holds the subject vehicle stationary by automatic brake control, and it resumes from standstill.
The system controls the longitudinal motion of the subject vehicle only. It adjusts vehicle speed to a driver-set speed, or to the speed required to keep a selected time gap to a target vehicle, whichever is lower. It commands the brake actuator and the powertrain actuator, and it presents its state to the driver.
What this document specifies
- The operating states of the ACC system and every transition between them.
- The nominal control behaviour: mode arbitration, target vehicle selection, standstill handling and resume.
- The numeric envelopes of vehicle motion: time gap, clearance, deceleration, jerk, acceleration and speed limits.
- The response of the system in defined driving scenarios taken from the Euro NCAP Assisted Driving protocol.
- The behaviour of the system when forward sensing, the vehicle bus or the actuators fail, and the limits that bound the authority of the system.
- For every requirement: an attribute set that makes the requirement traceable and verifiable, including the signal to log and the provenance of every number.
Layer
This is the system requirements layer of the development V, corresponding to Automotive SPICE PAM 4.0 process SYS.2 (System Requirements Analysis). Its counterpart on the right leg of the V is the system test specification (SYS.5), which is not part of this document. Requirements here state what the system does, never how it is implemented.
What this document deliberately excludes
| Excluded | Where it belongs |
| --- | --- |
| ISO 26262 in any form — ASIL assignment, hazard analysis, safety case, technical safety requirements as a distinct class | Out of project scope by fixed decision. Clause 7 of this document contains ordinary system requirements about safe behaviour, and nothing else |
| Lateral control, lane centring, steering intervention | A separate function. ACC here is longitudinal only |
| Autonomous emergency braking (AEB) behaviour | A separate system. This document specifies only how ACC yields the shared brake actuator to it (ACC-SYS-SAF-041) |
| Stakeholder requirements and the item definition | Assumed upstream (SYS.1); not produced here |
| Software-unit and hardware decomposition, system architecture | Downstream (SYS.3 and below) |
| Test cases, test procedures, pass/fail criteria beyond what each requirement states | The system test specification (SYS.5). The verified_by attribute of every requirement is deliberately empty in this revision |
| Vehicle owner-manual content, homologation and type approval | Out of scope, although ISO 15622:2018 cl. 5.1 requires the deceleration capability to be stated in the owner's manual |
Reading the verification tags
Every requirement carries a verification_tag recording how well the numbers in it are sourced. The vocabulary is defined in clause 3.4 and in Annex B. One value deserves attention on first reading: `UNVERIFIED-2018` marks a requirement whose number is an engineering assumption, because the clause exists in ISO 15622:2018 but its value could only be read from a superseded edition. Those requirements are collected in the assumptions register of clause 3.4 and their bounds are drawn dashed and labelled on figures F4 and F6.
- Clause number: 1

## R2: References (Document section)
2.1 Normative references
The following documents are referred to in the requirement text of clauses 5, 6 and 7 in such a way that some or all of their content constitutes requirements of this document.
| Reference | Title / edition | Source label | URL |
| --- | --- | --- | --- |
| ISO 15622:2018 | Intelligent transport systems — Adaptive cruise control systems — Performance requirements and test procedures. Third edition. Prepared by ISO/TC 204. Cancels and replaces ISO 15622:2010 and ISO 22179:2009 | Primary for the publisher-hosted preview, which reaches cl. 6.2.3; secondary or unverified beyond that point | https://www.iso.org/standard/71515.html |
| Euro NCAP AD v2.2 (2024-09) | Assisted Driving Highway Assist Test & Assessment Protocol, version 2.2, September 2024 | Primary (official protocol PDF) | https://cdn.euroncap.com/cars/assets/euro_ncap_ad_test_and_assessment_protocol_v22_71187c1b5e.pdf |
Edition caveat on ISO 15622:2018. The publisher-hosted official preview carries the full table of contents, clause 3 terms, clause 4 symbols, clause 5.1 Table 1 classification, cl. 6.1, cl. 6.2.1 and cl. 6.2.3.1, then truncates in cl. 6.2.3. Clauses 6.2.4 ("Go" transition), 6.3 (driver interface), 6.4 (operational limits), 6.5 (activation of brake lights), 6.6 (failure reactions), clause 7 (test procedures) and Annex A are not readable from any primary source retrieved for this project. Every requirement that depends on those clauses is tagged UNVERIFIED-2018 or DERIVED and appears in the assumptions register of clause 3.4.
Baseline caveat on Euro NCAP. v2.2 (2024-09) is the fixed scenario-parameter baseline of this project. It has been superseded: the current protocol is Assisted Driving Highway & Interurban Assist Systems v1.1 (2025-10), which delegates the ACC test procedures to a separate "Vehicle Assistance protocol" that was not retrieved. Where the newer protocol is known to differ, the difference is stated in the rationale of the affected requirement — see ACC-SYS-PRF-061.
2.2 Informative references
| Reference | What it is used for | Source label | URL |
| --- | --- | --- | --- |
| ISO 15622:2010 | Second edition. Source of the cl. 6.4 operational limits used as UNVERIFIED-2018 assumptions (deceleration, jerk, acceleration, minimum set speed) | Secondary — read from an unauthorised full-text copy; corroborated, never treated as the standard | https://www.iso.org/standard/50024.html |
| ISO/DIS 15622 (1999) | Draft international standard, ISO/TC 204/WG 14 N143.17, 1999-07-19. Source of the 100 ms brake-light timing; evidence that cl. 6.4 values move between drafts (it set 3,0 m/s², relaxed to 3,5 m/s² by publication) | Primary for that draft, superseded for the published editions | https://www.oocities.org/hyoungjin2001/AVS/ACC.pdf |
| ISO 15622:2002 | First edition. Evidence that the minimum time gap changed across editions (1 s in 2002, 0,8 s from 2010) | Primary (publisher-hosted preview of the superseded edition) | https://www.iso.org/standard/27834.html |
| EARS — Easy Approach to Requirements Syntax | The six requirement patterns used by the ears_pattern attribute. Canonical publication by the co-author of the method | Primary | https://alistairmavin.com/ears/ |
| INCOSE Guide for Writing Requirements (GtWR) | The Rxx requirement-writing rules cited in the rationale of individual requirements and enforced by the build. Named by Automotive SPICE PAM 4.0 SYS.2.BP1 note 01 as a source of defined requirement characteristics | Secondary — the official INCOSE summary sheet returned HTTP 403 and could not be retrieved, so rule texts come from a tool-vendor guide quoting the GtWR. No rule count is stated anywhere in this document, deliberately | https://www.incose.org/ |
| Automotive SPICE PAM 4.0 | Process reference for SYS.2. Output information item 17-54 Requirement attribute justifies the attribute schema of Annex B; SYS.2.BP1 note 02 justifies keeping verification criteria inside the requirement text rather than in a separate acceptance-criteria field | Secondary (accredited assessor provider summary of the paywalled VDA QMC publication) | https://www.automotivespice.com/ |
| Euro NCAP AD v1.1 (2025-10) | Current protocol; noted for staleness tracking only, not used as a parameter source | Primary | https://cdn.euroncap.com/cars/assets/euro_ncap_protocol_assisted_driving_v11_a6bfe1b5f2.pdf |
| OMG ReqIF 1.2 | Interchange format of the machine-readable export of this document. Namespace http://www.omg.org/spec/ReqIF/20110401/reqif.xsd. The schema tree is vendored at Reqs/export/schema/ | Primary | https://www.omg.org/spec/ReqIF/ |
2.3 Sources deliberately not used
| Not used | Why |
| --- | --- |
| UN Regulation No. 79 | Governs steering equipment and automatically commanded steering functions. Not a longitudinal ACC instrument |
| UN Regulation No. 157 (ALKS) | Covers automated lane keeping systems. Borrowing its deceleration thresholds into an ACC requirement would be a category error |
| NHTSA / FMVSS | There is no FMVSS for ACC and no NHTSA ACC performance test procedure. The NHTSA ACC work is human-factors research; the 2024 AEB final rule covers AEB, not ACC. Any claim that NHTSA specifies ACC numbers is unsupported |
| ISO 26262 (all parts) | Out of scope by fixed project decision — see clause 1 |
- Clause number: 2

## R3: Terms, definitions, symbols and assumptions (Document section)
3.1 Terms and definitions
Every term used in a requirement statement of clauses 5, 6 and 7 is defined here. The build fails if a requirement statement uses a controlled term that is absent from this table (INCOSE R4, "define terms"). Where ISO 15622:2018 defines the term, its clause is given and the definition follows the standard; the remaining terms are project definitions, marked (project).
| Term | Clause | Definition |
| --- | --- | --- |
| subject vehicle | ISO 15622:2018 cl. 3 | The vehicle in which the ACC system specified by this document is installed and whose longitudinal motion it controls |
| target vehicle | ISO 15622:2018 cl. 3.13 | The forward vehicle that the ACC system has selected to follow |
| forward vehicle | ISO 15622:2018 cl. 3 | A vehicle ahead of the subject vehicle and in the same lane, whether or not it is currently selected as the target vehicle |
| clearance | ISO 15622:2018 cl. 3 | The bumper-to-bumper longitudinal distance between the subject vehicle and the vehicle ahead of it |
| time gap | ISO 15622:2018 cl. 3 | The clearance divided by the speed of the subject vehicle, expressed in seconds |
| time gap setting | (project) | One of the discrete time gap values the driver may select; the ACC system regulates towards the selected setting |
| set speed | ISO 15622:2018 cl. 4 | The speed selected by the driver, denoted v_set, that the ACC system maintains when no target vehicle constrains it |
| speed control | ISO 15622:2018 cl. 3.12.2 | The control sub-state in which the ACC system regulates the subject vehicle to the set speed |
| following control | ISO 15622:2018 cl. 3.12.5 | The control sub-state in which the ACC system regulates the clearance or time gap to the target vehicle |
| hold state | ISO 15622:2018 cl. 3.12.6 | The state of an FSRA-type system in which automatic brake control keeps the subject vehicle stationary; realised in this document as the Active-Hold state |
| standstill | (project) | The condition in which the speed of the subject vehicle is zero |
| steady-state conditions | ISO 15622:2018 cl. 6.2.3.1 | Conditions in which the speeds of the subject vehicle and the target vehicle are constant and the clearance is settled, so that the regulated time gap can be measured |
| operating speed range | (project) | The subject vehicle speed interval over which the ACC system controls longitudinal motion, from standstill to the maximum set speed of ACC-SYS-PRF-041 |
| stationary object | ISO 15622:2018 cl. 3.14 | An object that is not moving along the centreline of the subject vehicle |
| stationary vehicle | (project) | A vehicle that is a stationary object |
| slow moving object | ISO 15622:2018 cl. 3.15 | An object moving along the centreline of the subject vehicle at less than MAX(1,0 m/s, 10 % of the subject vehicle speed) |
| lane change | Euro NCAP AD v2.2 (2024-09) | A full lateral transfer of a vehicle between adjacent lanes, with a 3,5 m lateral offset in the test scenarios of this document |
| time to collision | Euro NCAP AD v2.2 (2024-09) | The clearance divided by the relative closing speed, evaluated at the reference instant of a scenario |
| forward-sensing function | (project) | The function inside the system boundary of figure F1 that detects and tracks forward vehicles by fusing radar and camera data |
| target detected status | (project) | The binary indication of whether the ACC system currently has a target vehicle |
| forward-sensing health signal | (project) | The internal signal reporting the availability and plausibility of the forward-sensing function |
| vehicle bus health signal | (project) | The internal signal reporting whether the vehicle bus signals used for longitudinal control are being updated |
| actuation health signal | (project) | The internal signal reporting whether the brake actuator and the powertrain actuator are delivering the commanded longitudinal acceleration |
| vehicle bus signal | (project) | A signal received by the ACC system from the vehicle network, such as wheel speed, yaw rate, pedal position, brake switch or ignition status |
| longitudinal acceleration | (project) | The acceleration of the subject vehicle along its own centreline, positive forwards; a deceleration is a negative longitudinal acceleration and is stated in this document as a positive magnitude |
| commanded longitudinal acceleration | (project) | The longitudinal acceleration that the ACC system requests of the brake actuator and the powertrain actuator |
| automatic brake control | ISO 15622:2018 cl. 5.1 | Brake actuation commanded by the ACC system rather than by the driver |
| automatic service braking | (project) | Automatic brake control that produces a deceleration of the subject vehicle by the service brake |
| brake lights | ISO/DIS 15622 (1999) cl. 6.5 | The rear stop lamps of the subject vehicle |
| powertrain torque | (project) | The propulsion torque delivered at the driven wheels of the subject vehicle |
| accelerator pedal | (project) | The driver control whose position requests powertrain torque |
| brake pedal | (project) | The driver control whose actuation requests service braking |
| set switch | (project) | The driver control that activates the ACC system and adopts the current speed as the set speed |
| resume switch | (project) | The driver control that commands a resume from the Active-Hold state |
| cancel switch | (project) | The driver control that deactivates the ACC system to the Standby state |
| ignition | (project) | The vehicle power state that enables or disables the ACC system |
| driver | (project) | The person in the driving seat of the subject vehicle |
| hands-off condition | Euro NCAP AD v2.2 (2024-09) | The condition in which the driver is not detected as holding the steering wheel |
| takeover warning escalation | Euro NCAP AD v2.2 (2024-09) | The staged sequence of warnings that requests the driver to resume manual control |
| autonomous emergency braking system | (project) | The separate system, outside the ACC system boundary of figure F1, that commands the shared brake actuator to avoid or mitigate a collision |
| ACC state | (project) | The current operating state of the ACC system, one of the seven states of ACC-SYS-FUN-001 |
| Off | (project) | The state in which the ACC system is not powered and controls nothing |
| Standby | (project) | The state in which the ACC system is powered, controls nothing, and is available for activation |
| Active-Cruise | (project) | The active state in which the ACC system is in speed control |
| Active-Follow | (project) | The active state in which the ACC system is in following control |
| Active-Hold | (project) | The active state in which the ACC system holds the subject vehicle at standstill by automatic brake control; the realisation of the ISO 15622:2018 hold state |
| Driver-Override | (project) | The state in which driver accelerator input takes precedence over the powertrain request of the ACC system |
| Degraded-Fault | (project) | The state the ACC system enters when it has detected a fault that prevents it from meeting the requirements of clauses 5 and 6 |
3.2 Symbols
| Symbol | Meaning | Unit | Where fixed |
| --- | --- | --- | --- |
| tau_min | Minimum selectable time gap | s | ACC-SYS-PRF-001, 0,8 s |
| tau_max | Maximum selectable time gap | s | Not constrained by this document; the selectable band is ACC-SYS-PRF-002 |
| c_min | Minimum clearance floor at low speed, including standstill | m | ACC-SYS-PRF-003, 2,5 m (project choice) |
| v_low | Minimum operational speed for automatic positive acceleration | m/s | Deliberately not carried into a requirement for this FSRA system — see the assumptions register |
| v_set_min | Minimum selectable set speed | m/s | ACC-SYS-PRF-040, 7 m/s |
| v_set_max | Maximum selectable set speed | km/h | ACC-SYS-PRF-041, 180 km/h (project choice) |
| v_stopping | Target vehicle speed below which the stop-behind capability applies | m/s | ACC-SYS-PRF-042, 10 m/s |
| a_max | Maximum automatic acceleration | m/s² | ACC-SYS-PRF-022, 2,0 m/s² |
| d | Clearance between the subject vehicle and the vehicle ahead | m | Figures F3 and F4 |
3.3 Abbreviations
| Abbreviation | Expansion |
| --- | --- |
| ACC | Adaptive cruise control |
| ACC-SRS | ACC system requirements specification, the identifier of this document |
| AEB | Autonomous emergency braking |
| CCRb | Car-to-car rear braking (Euro NCAP scenario code) |
| CCRm | Car-to-car rear moving (Euro NCAP scenario code) |
| CCRs | Car-to-car rear stationary (Euro NCAP scenario code) |
| EARS | Easy Approach to Requirements Syntax |
| FSRA | Full speed range adaptive cruise control |
| GVT | Global vehicle target |
| HMI | Human-machine interface |
| LSRA | Limited speed range adaptive cruise control |
| PTW | Powered two-wheeler |
| SOV | Stationary or slower-moving other vehicle used in the cut-out scenario |
| SUT | System under test |
| TTC | Time to collision |
| VUT | Vehicle under test |
3.4 Assumptions register
This register is generated from the requirement YAML. It lists 28 requirements whose values are not confirmed ISO 15622:2018 numbers: 6 tagged `UNVERIFIED-2018` (the clause exists in the 2018 edition but the value could only be read from a superseded edition) and 22 tagged `DERIVED` (implied by another requirement, or a project choice no retrieved standard sets).
| Requirement | Clause | Tag | Value in the statement | Source | Owner / open action |
| --- | --- | --- | --- | --- | --- |
| ACC-SYS-FUN-001 | 5 | DERIVED | no numeric value | ISO 15622:2018 cl. 3.12.2; ISO 15622:2018 cl. 3.12.5; ISO 15622:2018 cl. 3.12.6; PROJECT-CHOICE:systems-engineer | systems-engineer |
| ACC-SYS-FUN-002 | 5 | DERIVED | no numeric value | PROJECT-CHOICE:systems-engineer | systems-engineer |
| ACC-SYS-FUN-003 | 5 | DERIVED | no numeric value | PROJECT-CHOICE:systems-engineer | systems-engineer |
| ACC-SYS-FUN-004 | 5 | DERIVED | no numeric value | ISO 15622:2018 cl. 6.1; PROJECT-CHOICE:systems-engineer | systems-engineer |
| ACC-SYS-FUN-006 | 5 | DERIVED | no numeric value | ISO 15622:2018 cl. 6.2.4; PROJECT-CHOICE:systems-engineer | systems-engineer |
| ACC-SYS-FUN-023 | 5 | DERIVED | no numeric value | ISO 15622:2018 cl. 6.1; PROJECT-CHOICE:systems-engineer | systems-engineer |
| ACC-SYS-FUN-060 | 5 | DERIVED | no numeric value | ISO 15622:2018 cl. 6.3; PROJECT-CHOICE:systems-engineer | systems-engineer |
| ACC-SYS-FUN-061 | 5 | UNVERIFIED-2018 | 100 ms | ISO/DIS 15622 (1999) cl. 6.5 | open action: confirm against ISO 15622:2018 (value read from ISO/DIS 15622 (1999) cl. 6.5) |
| ACC-SYS-PRF-003 | 6 | DERIVED | 2,5 m | ISO 15622:2018 cl. 6.2.3.1; PROJECT-CHOICE:systems-engineer | systems-engineer |
| ACC-SYS-PRF-020 | 6 | UNVERIFIED-2018 | 2 s, 3,5 m/s² | ISO 15622:2010 cl. 6.4 | open action: confirm against ISO 15622:2018 (value read from ISO 15622:2010 cl. 6.4) |
| ACC-SYS-PRF-021 | 6 | UNVERIFIED-2018 | 1 s, 2,5 m/s³ | ISO 15622:2010 cl. 6.4; ISO/DIS 15622 (1999) cl. 6.4 | open action: confirm against ISO 15622:2018 (value read from ISO 15622:2010 cl. 6.4; ISO/DIS 15622 (1999) cl. 6.4) |
| ACC-SYS-PRF-022 | 6 | UNVERIFIED-2018 | 2,0 m/s² | ISO 15622:2010 cl. 6.4; ISO/DIS 15622 (1999) cl. 6.4 | open action: confirm against ISO 15622:2018 (value read from ISO 15622:2010 cl. 6.4; ISO/DIS 15622 (1999) cl. 6.4) |
| ACC-SYS-PRF-040 | 6 | UNVERIFIED-2018 | 7 m/s | ISO 15622:2010 cl. 6.4; ISO/DIS 15622 (1999) cl. 6.4 | open action: confirm against ISO 15622:2018 (value read from ISO 15622:2010 cl. 6.4; ISO/DIS 15622 (1999) cl. 6.4) |
| ACC-SYS-PRF-041 | 6 | DERIVED | 180 km/h | ISO 15622:2018 cl. 4; PROJECT-CHOICE:systems-engineer | systems-engineer |
| ACC-SYS-PRF-060 | 6 | DERIVED | 120 km/h, 4,0 m/s², 0,5 m | Euro NCAP AD v2.2 (2024-09) §ACC car-to-car rear braking; PROJECT-CHOICE:systems-engineer | systems-engineer |
| ACC-SYS-PRF-061 | 6 | DERIVED | 3,00 s, 0,5 m | Euro NCAP AD v2.2 (2024-09) §ACC cut-out; PROJECT-CHOICE:systems-engineer | systems-engineer |
| ACC-SYS-PRF-062 | 6 | DERIVED | 0,5 s | ISO 15622:2018 cl. 6.1; Euro NCAP AD v2.2 (2024-09) §ACC cut-out; PROJECT-CHOICE:systems-engineer | systems-engineer |
| ACC-SYS-SAF-001 | 7 | DERIVED | 300 ms | ISO 15622:2018 cl. 6.6; PROJECT-CHOICE:systems-engineer | systems-engineer |
| ACC-SYS-SAF-002 | 7 | DERIVED | 200 ms, 100 ms | PROJECT-CHOICE:systems-engineer | systems-engineer |
| ACC-SYS-SAF-003 | 7 | DERIVED | 1,0 m/s², 500 ms, 200 ms | ISO 15622:2018 cl. 6.6; PROJECT-CHOICE:systems-engineer | systems-engineer |
| ACC-SYS-SAF-004 | 7 | DERIVED | 500 ms | ISO 15622:2018 cl. 6.3; ISO 15622:2018 cl. 6.6; PROJECT-CHOICE:systems-engineer | systems-engineer |
| ACC-SYS-SAF-021 | 7 | DERIVED | 500 ms, 200 ms | PROJECT-CHOICE:systems-engineer | systems-engineer |
| ACC-SYS-SAF-022 | 7 | DERIVED | 200 ms | DERIVED-FROM:ACC-SYS-SAF-021; PROJECT-CHOICE:systems-engineer | implied by ACC-SYS-SAF-021; systems-engineer |
| ACC-SYS-SAF-023 | 7 | DERIVED | 500 ms | PROJECT-CHOICE:systems-engineer | systems-engineer |
| ACC-SYS-SAF-024 | 7 | UNVERIFIED-2018 | 2,5 m/s³ | ISO 15622:2010 cl. 6.4; DERIVED-FROM:ACC-SYS-PRF-021 | implied by ACC-SYS-PRF-021; open action: confirm against ISO 15622:2018 (value read from ISO 15622:2010 cl. 6.4) |
| ACC-SYS-SAF-040 | 7 | DERIVED | 5,0 m/s² | Euro NCAP AD v2.2 (2024-09) §ACC-vs-AEB demarcation; PROJECT-CHOICE:systems-engineer | systems-engineer |
| ACC-SYS-SAF-041 | 7 | DERIVED | 0,0 m/s² | Euro NCAP AD v2.2 (2024-09) §ACC-vs-AEB demarcation; PROJECT-CHOICE:systems-engineer | systems-engineer |
| ACC-SYS-SAF-042 | 7 | DERIVED | no numeric value | PROJECT-CHOICE:systems-engineer | systems-engineer |
Provenance chain per requirement, quoted from its rationale:
- ACC-SYS-FUN-001 — ISO 15622:2018 defines ACC behaviour as a set of control sub-states, the speed control sub-state (cl.
- ACC-SYS-FUN-002 — The ACC system needs a defined powered but inactive condition from which the driver can activate it, and a defined entry into that condition.
- ACC-SYS-FUN-003 — Every state of ACC-SYS-FUN-001 needs a defined exit to the unpowered condition, otherwise the state machine of figure F2 has no path back to Off and the Degraded-Fault state is a sink.
- ACC-SYS-FUN-004 — ISO 15622:2018 cl.
- ACC-SYS-FUN-006 — ISO 15622:2018 cl.
- ACC-SYS-FUN-023 — ISO 15622:2018 cl.
- ACC-SYS-FUN-060 — ISO 15622:2018 cl.
- ACC-SYS-FUN-061 — Engineering assumption, not a confirmed 2018 value.
- ACC-SYS-PRF-003 — ISO 15622:2018 cl.
- ACC-SYS-PRF-020 — Engineering assumption, not a confirmed 2018 value.
- ACC-SYS-PRF-021 — Engineering assumption, not a confirmed 2018 value.
- ACC-SYS-PRF-022 — Engineering assumption, not a confirmed 2018 value.
- ACC-SYS-PRF-040 — Engineering assumption, not a confirmed 2018 value.
- ACC-SYS-PRF-041 — ISO 15622:2018 cl.
- ACC-SYS-PRF-060 — The scenario is the Euro NCAP Assisted Driving car-to-car rear braking case, CCRb, with the lead vehicle braking at 4 m/s² at 100 % overlap; the deceleration value and the 120 km/h subject vehicle speed are read verbatim from Euro NCAP AD v2.2 (2024-09), which is the fixed scenario baseline of this project.
- ACC-SYS-PRF-061 — The scenario is the Euro NCAP Assisted Driving cut-out case: the lead vehicle performs a full lane change out of the lane of the vehicle under test with a 3,5 m lateral offset, revealing a stationary target, with the reference instant at a time to collision of 3,00 s.
- ACC-SYS-PRF-062 — ISO 15622:2018 cl.
- ACC-SYS-SAF-001 — ISO 15622:2018 cl.
- ACC-SYS-SAF-002 — No retrieved clause of ISO 15622:2018 addresses vehicle bus signal timeouts; cl.
- ACC-SYS-SAF-003 — Loss of brake or powertrain actuation authority is a cl.
- ACC-SYS-SAF-004 — ISO 15622:2018 cl.
- ACC-SYS-SAF-021 — ISO 15622:2018 cl.
- ACC-SYS-SAF-022 — Companion to ACC-SYS-SAF-021 for the two fault sources that do not come from forward sensing: the vehicle bus health signal set by ACC-SYS-SAF-002 and the actuation health signal set by ACC-SYS-SAF-003.
- ACC-SYS-SAF-023 — Without this requirement the Degraded-Fault state is a sink from which only an ignition cycle escapes, which would make a recovered transient fault permanently disabling.
- ACC-SYS-SAF-024 — Engineering assumption, not a confirmed 2018 value.
- ACC-SYS-SAF-040 — This is an authority boundary, not a comfort limit: it separates the braking domain of ACC from autonomous emergency braking, which shares the brake actuator (see figure F1).
- ACC-SYS-SAF-041 — ACC and autonomous emergency braking share one brake actuator, shown crossing the system boundary in figure F1, so the arbitration between them has to be specified somewhere and this artifact is the system-layer document that owns the ACC side of it.
- ACC-SYS-SAF-042 — ACC-SYS-FUN-004 activates the system on a driver set command from the Standby state; this requirement closes the corresponding path from the Degraded-Fault state so that a driver cannot activate longitudinal control while the system knows it cannot deliver it.
- Clause number: 3

## R4: System overview (Document section)
4.1 The system and its boundary
The ACC system fuses radar and camera data into a set of tracked forward vehicles, selects one of them as the target vehicle, and computes a longitudinal acceleration request that it issues to the brake actuator and the powertrain actuator. A state manager decides whether the system is controlling the vehicle at all; a fault manager decides whether it is allowed to; an HMI arbitration function decides what the driver is told. Everything else — the driver, the target vehicle, the actuators themselves and the autonomous emergency braking system that shares the brake actuator — is outside the boundary.
Figure F1 fixes that boundary. It matters for two reasons. First, the phrase "the ACC system" that opens almost every requirement in this document means exactly what is inside the box in F1 and nothing else. Second, the arrows crossing the boundary carry the signal names used in the measurand attribute of every requirement whose verification_method is Test, so F1 is also the signal dictionary for the later test specification.
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4.2 System classification
The system is of FSRA type per ISO 15622:2018 cl. 5.1 Table 1: no manual clutch dependency, active brake control, operation down to standstill. That classification is what puts three behaviours in scope that an LSRA system would not have: the transition into a hold state within 3 s of standstill (ACC-SYS-FUN-005), the stop-behind capability for a gradually stopping target vehicle (ACC-SYS-PRF-042), and the resume from standstill (ACC-SYS-FUN-006).
The classification also removes one requirement that a naive reading of ISO 15622 cl. 6.4 would add. That clause requires a minimum operational speed v_low of 5 m/s for automatic positive acceleration. Applying it here would forbid the resume of ACC-SYS-FUN-006, because a resume from standstill is automatic positive acceleration below 5 m/s. The 2018 foreword resolves the conflict in favour of the resume: it records that "automatic start from hold is no longer prohibited". The v_low floor is therefore not carried into any requirement of this document, and the omission is recorded in the assumptions register of clause 3.4.
4.3 Operating states
The ACC system has seven operating states, fixed by ACC-SYS-FUN-001. Three of them map onto sub-states defined by ISO 15622:2018 — Active-Cruise onto the speed control sub-state (cl. 3.12.2), Active-Follow onto the following control sub-state (cl. 3.12.5), Active-Hold onto the FSRA hold state (cl. 3.12.6). Off and Standby are the inactive conditions. Driver-Override carries the pedal precedence of cl. 6.3.1. Degraded-Fault carries the failure reactions of cl. 6.6.
Figure F2 shows all seven states and every transition between them. Every arc carries its trigger and the identifier of the single requirement that specifies it; an arc with no requirement identifier would be a defect in this document, and the build enforces the cross-check in both directions.
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Within the active group, Active-Cruise and Active-Follow are not driver-selected: the ACC system arbitrates between them automatically, taking whichever of the set speed and the following speed is lower (ACC-SYS-FUN-021), and it makes the transition without driver input (ACC-SYS-FUN-022). Active-Hold is entered from Active-Follow within 3 s of standstill and left on a driver resume command.
4.4 Control objective in following control
In following control the ACC system regulates the clearance to the target vehicle. The desired clearance is the greater of a fixed floor c_min and the product of the selected time gap setting and the subject vehicle speed, which makes the desired clearance a constant at low speed and proportional to speed above the knee at v = c_min / tau. Figure F3 dimensions the geometry and plots the relation, with the 0,8 s floor of ACC-SYS-PRF-001 and the 1,5 s to 2,2 s selectable band of ACC-SYS-PRF-002 marked on the inset.
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4.5 Requirement-writing conventions in force
| Convention | Rule |
| --- | --- |
| Modal verb | Every requirement contains exactly one `shall`. should and may do not appear in any requirement statement in this document, because a recommendation and a permission are not requirements |
| Pattern | Every requirement statement follows one of the six EARS patterns, declared in its ears_pattern attribute. While opens a state-driven precondition, When a trigger, If ... then an unwanted-behaviour response, Where an optional feature |
| Singularity | One requirement states one capability. Combinators (and, or) may appear in a precondition or a trigger, because EARS preconditions are explicitly plural, but never join two responses (INCOSE R19, R20). The build enforces this |
| Quantification | Every quantity carries a unit from the set s, ms, m, m/s, m/s², m/s³, km/h, %, °. No requirement contains an unquantified adjective such as "smooth", "safe" or "quickly" (R7, R36) |
| Decimal separator | Decimal comma, matching ISO 15622 usage: 0,8 s, 3,5 m/s². Unit exponents are written m/s² and m/s³ in prose and [m/s^2] in measurand values, which are machine-read |
| Rationale | Purpose, provenance and trade-off live in the rationale attribute, never inside the shall statement (R22) |
| Verification criteria | Inherent in the requirement text, per Automotive SPICE PAM 4.0 SYS.2.BP1 note 02. There is no separate acceptance-criteria field, and the measurand attribute deliberately names signals and units without thresholds |
| Figures | Illustrative only. Removing a figure never makes a requirement untestable; if it would, the requirement is defective |
| Identifiers | ACC-SYS-<GRP>-<nnn>, immutable, never reused, gaps legal. A requirement that moves chapter is retired and reissued, never renumbered |
- Clause number: 4

## R5: Functional and HMI requirements (Document section)
This clause carries 13 requirements with identifiers ACC-SYS-FUN-###, ordered by identifier and grouped into 4 sub-clauses that follow the identifier allocation blocks.
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- Clause number: 5

### R6: States and nominal transitions (Document section)
Identifier block 001-019. Requirements in this sub-clause: ACC-SYS-FUN-001, ACC-SYS-FUN-002, ACC-SYS-FUN-003, ACC-SYS-FUN-004, ACC-SYS-FUN-005, ACC-SYS-FUN-006.
- Clause number: 5.1

#### ACC-SYS-FUN-001: Operating state set (ACC System Requirement)
- Chapter: Functional-HMI
- Requirement text: The ACC system shall provide the operating states Off, Standby, Active-Cruise, Active-Follow, Active-Hold, Driver-Override and Degraded-Fault.
- EARS pattern: Ubiquitous
- Applicable states: Off, Standby, Active-Cruise, Active-Follow, Active-Hold, Driver-Override, Degraded-Fault
- Rationale: ISO 15622:2018 defines ACC behaviour as a set of control sub-states, the speed control sub-state (cl. 3.12.2), the following control sub-state (cl. 3.12.5) and the FSRA hold state (cl. 3.12.6), and cl. 6.1 requires an FSRA-type system to change into the hold state after standstill. The standard does not enumerate a complete state set for an implementation, so the seven-state set is project-owned: Off, Standby, Active-Cruise, Active-Follow and Active-Hold map onto the sub-states of the standard plus the inactive conditions, Driver-Override carries the cl. 6.3.1 pedal precedence, and Degraded-Fault carries the cl. 6.6 failure reactions. Overlap rule O2 places the existence of every state, including Degraded-Fault, in the Functional chapter. Owned by the systems engineer, 2026-08-18.
- Source: ISO 15622:2018 cl. 3.12.2; ISO 15622:2018 cl. 3.12.5; ISO 15622:2018 cl. 3.12.6; PROJECT-CHOICE:systems-engineer
- Verification tag: DERIVED
- Verification method: Inspection
- Status: Draft
- Revision: 1.0
- Figures: F2
- Related: ACC-SYS-FUN-002, ACC-SYS-FUN-005, ACC-SYS-SAF-021

#### ACC-SYS-FUN-002: Entry to Standby on ignition on (ACC System Requirement)
- Chapter: Functional-HMI
- Requirement text: When the ignition is switched on, the ACC system shall enter the Standby state.
- EARS pattern: EventDriven
- Applicable states: Off, Standby
- Rationale: The ACC system needs a defined powered but inactive condition from which the driver can activate it, and a defined entry into that condition. No retrieved clause of ISO 15622:2018 specifies the power-on state, so the choice of Standby rather than Off after ignition on is project-owned; it is the behaviour that makes the cl. 6.2.1 activation transition reachable without a separate main switch. Owned by the systems engineer, 2026-08-18.
- Source: PROJECT-CHOICE:systems-engineer
- Verification tag: DERIVED
- Verification method: Test
- Measurand: ignition [bool]; acc_state [enum]
- Status: Draft
- Revision: 1.0
- Figures: F2
- Related: ACC-SYS-FUN-001, ACC-SYS-FUN-003, ACC-SYS-FUN-004

#### ACC-SYS-FUN-003: Entry to Off on ignition off (ACC System Requirement)
- Chapter: Functional-HMI
- Requirement text: When the ignition is switched off, the ACC system shall enter the Off state.
- EARS pattern: EventDriven
- Applicable states: Off, Standby, Active-Cruise, Active-Follow, Active-Hold, Driver-Override, Degraded-Fault
- Rationale: Every state of ACC-SYS-FUN-001 needs a defined exit to the unpowered condition, otherwise the state machine of figure F2 has no path back to Off and the Degraded-Fault state is a sink. No retrieved clause of ISO 15622:2018 specifies the power-down behaviour, so the transition is project-owned. Release of brake force on this transition is bounded separately by ACC-SYS-SAF-024, because combining a state transition with an actuator constraint would make this requirement compound (INCOSE R19). Owned by the systems engineer, 2026-08-18.
- Source: PROJECT-CHOICE:systems-engineer
- Verification tag: DERIVED
- Verification method: Test
- Measurand: ignition [bool]; acc_state [enum]
- Status: Draft
- Revision: 1.0
- Figures: F2
- Related: ACC-SYS-FUN-002, ACC-SYS-SAF-024

#### ACC-SYS-FUN-004: Activation to Active-Cruise on driver set command (ACC System Requirement)
- Chapter: Functional-HMI
- Requirement text: While the ACC system is in the Standby state, when the driver operates the set switch, the ACC system shall enter the Active-Cruise state.
- EARS pattern: Complex
- Applicable states: Standby, Active-Cruise
- Rationale: ISO 15622:2018 cl. 6.1 describes the active condition in which vehicle speed is controlled automatically, and cl. 6.3 covers the driver interface, but the driver-interface content is past the truncation point of the publisher-hosted preview, so no standardised activation command is available. Activation on a driver set command is project-owned. Activation while a fault is present is inhibited by ACC-SYS-SAF-042, which is a separate requirement because its trigger is a fault (overlap rule O2). Owned by the systems engineer, 2026-08-18.
- Source: ISO 15622:2018 cl. 6.1; PROJECT-CHOICE:systems-engineer
- Verification tag: DERIVED
- Verification method: Test
- Measurand: set_switch [bool]; acc_state [enum]; v_set [m/s]
- Status: Draft
- Revision: 1.0
- Figures: F2
- Related: ACC-SYS-FUN-021, ACC-SYS-SAF-042

#### ACC-SYS-FUN-005: Entry to Active-Hold after standstill (ACC System Requirement)
- Chapter: Functional-HMI
- Requirement text: When the subject vehicle reaches standstill while the ACC system is in the Active-Follow state, the ACC system shall enter the Active-Hold state within 3 s of standstill.
- EARS pattern: EventDriven
- Applicable states: Active-Follow, Active-Hold
- Rationale: ISO 15622:2018 cl. 6.1 requires an FSRA-type system to change from following control to the hold state within a time period not to exceed 3 s after the subject vehicle has come to a stop, and to keep the vehicle stationary by automatic brake control in that state. The 3 s value is read verbatim from the publisher-hosted 2018 preview and is one of the few clause-6 numbers confirmed for the current edition. The clearance held in the Active-Hold state is specified by ACC-SYS-PRF-003.
- Source: ISO 15622:2018 cl. 6.1
- Verification tag: VERIFIED-PRIMARY
- Verification method: Test
- Measurand: v_ego [m/s]; acc_state [enum]; t [s]
- Status: Draft
- Revision: 1.0
- Figures: F2
- Related: ACC-SYS-FUN-006, ACC-SYS-PRF-003, ACC-SYS-PRF-042

#### ACC-SYS-FUN-006: Driver-commanded resume from Active-Hold (ACC System Requirement)
- Chapter: Functional-HMI
- Requirement text: While the ACC system is in the Active-Hold state, when the driver operates the resume switch, the ACC system shall enter the Active-Follow state.
- EARS pattern: Complex
- Applicable states: Active-Hold, Active-Follow
- Rationale: ISO 15622:2018 cl. 6.2.4 is the resume-from-standstill clause, titled the Go transition, but its content is past the truncation point of the publisher-hosted preview, so no standardised resume trigger or timing is available. The only verified 2018 statement about it is the foreword change note that automatic start from hold is no longer prohibited, which is a permission and not a requirement. A driver resume command is therefore specified as the guaranteed path out of the hold state, and it is project-owned. The hands-off escalation that must precede a resume is carried by ACC-SYS-SAF-060. Owned by the systems engineer, 2026-08-18.
- Source: ISO 15622:2018 cl. 6.2.4; PROJECT-CHOICE:systems-engineer
- Verification tag: DERIVED
- Verification method: Test
- Measurand: resume_switch [bool]; acc_state [enum]; v_ego [m/s]
- Status: Draft
- Revision: 1.0
- Figures: F2
- Related: ACC-SYS-FUN-005, ACC-SYS-SAF-060

### R7: Control-mode arbitration and target selection (Document section)
Identifier block 020-039. Requirements in this sub-clause: ACC-SYS-FUN-021, ACC-SYS-FUN-022, ACC-SYS-FUN-023.
- Clause number: 5.2

#### ACC-SYS-FUN-021: Control-mode arbitration between set speed and following (ACC System Requirement)
- Chapter: Functional-HMI
- Requirement text: While the ACC system is in the Active-Cruise state or the Active-Follow state, the ACC system shall control the subject vehicle speed to the lower of the set speed and the speed required to maintain the selected time gap to the target vehicle.
- EARS pattern: StateDriven
- Applicable states: Active-Cruise, Active-Follow
- Rationale: ISO 15622:2018 cl. 6.1 states that when ACC is active the vehicle speed shall be controlled automatically either to maintain a clearance to a forward vehicle or to maintain the set speed, whichever speed is lower, and cl. 6.2.1 states the transition between the two control modes shall be made automatically. This requirement fixes the arbitration; the automatic-transition obligation is carried separately by ACC-SYS-FUN-022 so that neither statement is compound (INCOSE R19). The phrase "the lower of A and B" is a single selection response, not two combined responses, so R20 is satisfied.
- Source: ISO 15622:2018 cl. 6.1; ISO 15622:2018 cl. 6.2.1
- Verification tag: VERIFIED-PRIMARY
- Verification method: Test
- Measurand: v_ego [m/s]; v_set [m/s]; d_clearance [m]; acc_control_mode [enum]
- Status: Draft
- Revision: 1.0
- Figures: F2, F3
- Related: ACC-SYS-FUN-022, ACC-SYS-PRF-001, ACC-SYS-PRF-003

#### ACC-SYS-FUN-022: Automatic transition between control modes (ACC System Requirement)
- Chapter: Functional-HMI
- Requirement text: While the ACC system is in the Active-Cruise state or the Active-Follow state, the ACC system shall change between speed control and following control without driver input.
- EARS pattern: StateDriven
- Applicable states: Active-Cruise, Active-Follow
- Rationale: ISO 15622:2018 cl. 6.2.1 states verbatim that the transition between the control modes, following controlled or speed controlled, shall be made automatically, and cl. 6.1 states that the change between the two control modes is made automatically by the ACC system. Read from the publisher-hosted 2018 preview. This requirement carries only the automatic-transition obligation; which mode wins is carried by ACC-SYS-FUN-021 (INCOSE R19). The phrase "between speed control and following control" names the two endpoints of one transition, not two responses, so R20 is satisfied.
- Source: ISO 15622:2018 cl. 6.1; ISO 15622:2018 cl. 6.2.1
- Verification tag: VERIFIED-PRIMARY
- Verification method: Test
- Measurand: acc_control_mode [enum]; target_detected [bool]; v_ego [m/s]
- Status: Draft
- Revision: 1.0
- Figures: F2
- Related: ACC-SYS-FUN-021, ACC-SYS-FUN-023

#### ACC-SYS-FUN-023: Target vehicle selection among forward vehicles (ACC System Requirement)
- Chapter: Functional-HMI
- Requirement text: While the ACC system is in the Active-Cruise state or the Active-Follow state and more than one forward vehicle is present in the subject vehicle lane, the ACC system shall select as the target vehicle the forward vehicle with the smallest clearance to the subject vehicle.
- EARS pattern: StateDriven
- Applicable states: Active-Cruise, Active-Follow
- Rationale: ISO 15622:2018 cl. 6.1 states verbatim that if there is more than one forward vehicle, the one to be followed shall be selected automatically, and refers to cl. 6.2.3.3 for the selection detail; that sub-clause is past the truncation point of the publisher-hosted preview, so the selection criterion itself is project-owned. Smallest clearance is chosen because it is the criterion that makes the following-control requirements of ACC-SYS-PRF-001 and ACC-SYS-PRF-003 conservative for the closest vehicle. This rule also governs which vehicle becomes the target after a cut-in or a cut-out, so no separate reselection rule exists (INCOSE R32); the latency of a reselection is carried by ACC-SYS-PRF-062. Owned by the systems engineer, 2026-08-18.
- Source: ISO 15622:2018 cl. 6.1; PROJECT-CHOICE:systems-engineer
- Verification tag: DERIVED
- Verification method: Test
- Measurand: target_id [enum]; d_clearance [m]; v_target [m/s]
- Status: Draft
- Revision: 1.0
- Figures: F3, F5
- Related: ACC-SYS-FUN-021, ACC-SYS-PRF-062

### R8: Driver commands and override (Document section)
Identifier block 040-059. Requirements in this sub-clause: ACC-SYS-FUN-041, ACC-SYS-FUN-042.
- Clause number: 5.3

#### ACC-SYS-FUN-041: Accelerator pedal override precedence (ACC System Requirement)
- Chapter: Functional-HMI
- Requirement text: While the driver accelerator pedal position requests a powertrain torque greater than the powertrain torque requested by the ACC system, the ACC system shall be in the Driver-Override state.
- EARS pattern: StateDriven
- Applicable states: Active-Cruise, Active-Follow, Active-Hold, Driver-Override
- Rationale: ISO 15622:2018 cl. 6.3.1 places driver override precedence in the standard, accelerator input taking priority over ACC engine control, but the clause is past the truncation point of the publisher-hosted preview and was read from the ISO/TC 204 community extract, a non-official source, hence VERIFIED-SECONDARY. The requirement is written as a state invariant rather than as an entry event and an exit event, so that one statement specifies both the entry to and the exit from the Driver-Override state without becoming compound (INCOSE R19). Overlap rule O5 places driver pedal override in the Functional chapter: the driver is commanding and nothing is wrong. Brake pedal input is handled by ACC-SYS-FUN-042 because its response is a different state.
- Source: ISO 15622:2018 cl. 6.3.1
- Verification tag: VERIFIED-SECONDARY
- Verification method: Test
- Measurand: accel_pedal_pos [%]; a_x_cmd_acc [m/s^2]; acc_state [enum]
- Status: Draft
- Revision: 1.0
- Figures: F1, F2
- Related: ACC-SYS-FUN-042, ACC-SYS-FUN-060

#### ACC-SYS-FUN-042: Deactivation to Standby on driver cancel command (ACC System Requirement)
- Chapter: Functional-HMI
- Requirement text: While the ACC system is in the Active-Cruise state, the Active-Follow state or the Active-Hold state, when the driver depresses the brake pedal or operates the cancel switch, the ACC system shall enter the Standby state.
- EARS pattern: Complex
- Applicable states: Active-Cruise, Active-Follow, Active-Hold, Standby
- Rationale: ISO 15622:2018 cl. 6.3.1 places driver braking precedence over ACC braking in the standard; the clause is past the truncation point of the publisher-hosted preview and was read from the ISO/TC 204 community extract, hence VERIFIED-SECONDARY. The cancel switch is the second deactivation trigger and is project-owned. Both triggers are carried by one requirement because they are alternative conditions on one response, the entry to Standby; INCOSE R20 forbids combining two responses, not two trigger conditions. Release of brake force on this transition is bounded by ACC-SYS-SAF-024.
- Source: ISO 15622:2018 cl. 6.3.1; PROJECT-CHOICE:systems-engineer
- Verification tag: VERIFIED-SECONDARY
- Verification method: Test
- Measurand: brake_pedal_switch [bool]; cancel_switch [bool]; acc_state [enum]
- Status: Draft
- Revision: 1.0
- Figures: F1, F2
- Related: ACC-SYS-FUN-041, ACC-SYS-SAF-024

### R9: HMI indication and discrete outputs (Document section)
Identifier block 060-079. Requirements in this sub-clause: ACC-SYS-FUN-060, ACC-SYS-FUN-061.
- Clause number: 5.4

#### ACC-SYS-FUN-060: Driver indication of ACC status (ACC System Requirement)
- Chapter: Functional-HMI
- Requirement text: While the ACC system is in the Standby state, the Active-Cruise state, the Active-Follow state, the Active-Hold state, the Driver-Override state or the Degraded-Fault state, the ACC system shall indicate to the driver the ACC state, the set speed, the selected time gap setting and the target detected status.
- EARS pattern: StateDriven
- Applicable states: Standby, Active-Cruise, Active-Follow, Active-Hold, Driver-Override, Degraded-Fault
- Rationale: ISO 15622:2018 cl. 6.3 covers the driver interface but its content is past the truncation point of the publisher-hosted preview, so no standardised display content list is available. The four indicated quantities are the information the driver needs to predict ACC behaviour: the state determines whether ACC is controlling the vehicle, the set speed and the time gap setting determine the target of that control, and the target detected status distinguishes speed control from following control. They form one indication set presented by one function, so this is a singular requirement under INCOSE R19; the enumeration is the object of one response, not four responses. Overlap rule O4 places nominal-state indication in the Functional chapter; fault annunciation is ACC-SYS-SAF-004. Owned by the systems engineer, 2026-08-18.
- Source: ISO 15622:2018 cl. 6.3; PROJECT-CHOICE:systems-engineer
- Verification tag: DERIVED
- Verification method: Demonstration
- Status: Draft
- Revision: 1.0
- Figures: F1
- Related: ACC-SYS-FUN-021, ACC-SYS-SAF-004

#### ACC-SYS-FUN-061: Brake light illumination on automatic braking (ACC System Requirement)
- Chapter: Functional-HMI
- Requirement text: When the ACC system initiates automatic service braking of the subject vehicle, the ACC system shall illuminate the brake lights within 100 ms of that initiation.
- EARS pattern: EventDriven
- Applicable states: Active-Cruise, Active-Follow, Active-Hold
- Rationale: Engineering assumption, not a confirmed 2018 value. ISO 15622:2018 cl. 6.5 is titled Activation of brake lights and its existence and title are confirmed from the table of contents of the publisher-hosted 2018 preview, but the preview truncates in cl. 6.2.3 and never reaches cl. 6.5, so the 2018 timing could not be read from any primary source. The 100 ms value is verbatim from ISO/DIS 15622 (1999) cl. 6.5, a verbatim copy of the draft international standard, which is primary for that draft and superseded for the published editions. The value is therefore tagged UNVERIFIED-2018; obtaining ISO 15622:2018 cl. 6.5 and confirming the timing is an open action in the assumptions register. Overlap rule O3 places a latency on a discrete output in the Functional chapter.
- Source: ISO/DIS 15622 (1999) cl. 6.5
- Verification tag: UNVERIFIED-2018
- Verification method: Test
- Measurand: brake_light [bool]; a_x_cmd_acc [m/s^2]; t [s]
- Status: Draft
- Revision: 1.0
- Figures: F1
- Related: ACC-SYS-PRF-020, ACC-SYS-SAF-040

## R10: Performance requirements (Document section)
This clause carries 12 requirements with identifiers ACC-SYS-PRF-###, ordered by identifier and grouped into 4 sub-clauses that follow the identifier allocation blocks.
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- Clause number: 6

### R11: Time gap and clearance (Document section)
Identifier block 001-019. Requirements in this sub-clause: ACC-SYS-PRF-001, ACC-SYS-PRF-002, ACC-SYS-PRF-003.
- Clause number: 6.1

#### ACC-SYS-PRF-001: Minimum selectable time gap (ACC System Requirement)
- Chapter: Performance
- Requirement text: While the ACC system is in the Active-Follow state under steady-state conditions, the ACC system shall maintain a time gap to the target vehicle of not less than 0,8 s at every subject vehicle speed within the operating speed range.
- EARS pattern: StateDriven
- Applicable states: Active-Follow
- Rationale: ISO 15622:2018 cl. 6.2.3.1 states verbatim that the minimum selectable time gap for following control mode under steady-state conditions for all speeds v shall be greater than or equal to 0,8 s. Read from the publisher-hosted 2018 preview, which reaches this clause. Note the value changed across editions, the 2002 first edition required a minimum of 1 s, so the edition is stated explicitly. The phrase "every subject vehicle speed within the operating speed range" replaces the phrase "all speeds" of the standard to avoid the universal qualifier flagged by INCOSE R34 while preserving the intent of the standard.
- Source: ISO 15622:2018 cl. 6.2.3.1
- Verification tag: VERIFIED-PRIMARY
- Verification method: Test
- Measurand: tau_gap [s]; d_clearance [m]; v_ego [m/s]
- Status: Draft
- Revision: 1.0
- Figures: F3
- Related: ACC-SYS-PRF-002, ACC-SYS-PRF-003, ACC-SYS-FUN-021

#### ACC-SYS-PRF-002: Selectable time gap setting range (ACC System Requirement)
- Chapter: Performance
- Requirement text: The ACC system shall provide at least one selectable time gap setting within the range 1,5 s to 2,2 s for subject vehicle speeds greater than 8 m/s.
- EARS pattern: Ubiquitous
- Applicable states: Standby, Active-Cruise, Active-Follow
- Rationale: ISO 15622:2018 cl. 6.2.3.1 states verbatim that at least one selectable time gap setting shall be in the range 1,5 s to 2,2 s for speeds greater than 8 m/s. Read from the publisher-hosted 2018 preview. The speed qualifier is new in the 2018 edition; the 2002 first edition carried the same band with no speed qualifier, so the qualifier is retained here to match the current edition. This requirement fixes the setting range only; the floor on the resulting time gap is ACC-SYS-PRF-001.
- Source: ISO 15622:2018 cl. 6.2.3.1
- Verification tag: VERIFIED-PRIMARY
- Verification method: Test
- Measurand: tau_gap [s]; gap_setting [enum]; v_ego [m/s]
- Status: Draft
- Revision: 1.0
- Figures: F3
- Related: ACC-SYS-PRF-001, ACC-SYS-PRF-003, ACC-SYS-FUN-060

#### ACC-SYS-PRF-003: Minimum steady-state clearance (ACC System Requirement)
- Chapter: Performance
- Requirement text: While the ACC system is in the Active-Follow state or the Active-Hold state under steady-state conditions, the ACC system shall maintain a clearance to the target vehicle of not less than the greater of 2,5 m and the product of the selected time gap setting and the subject vehicle speed.
- EARS pattern: StateDriven
- Applicable states: Active-Follow, Active-Hold
- Rationale: ISO 15622:2018 cl. 6.2.3.1 gives the minimum steady-state clearance as MAX(c_min, tau_min times v) and states that the clearance may temporarily fall below that value under transient conditions, after which the system shall adjust the clearance to attain the desired clearance. The relation is read verbatim from the publisher-hosted 2018 preview and is VERIFIED-PRIMARY, but the standard defines c_min as a symbol in cl. 4 without setting a numeric value, so the 2,5 m standstill clearance is project-owned; the requirement therefore carries the weaker DERIVED tag because its weakest constituent is a project choice. 2,5 m is chosen as a bumper-to-bumper clearance that keeps a stopped subject vehicle outside the crush zone of the target vehicle and leaves room for creep on a gradient. The same floor governs the Active-Hold state, which is why ACC-SYS-FUN-005 refers to this requirement for the held clearance. Owned by the systems engineer, 2026-08-18.
- Source: ISO 15622:2018 cl. 6.2.3.1; PROJECT-CHOICE:systems-engineer
- Verification tag: DERIVED
- Verification method: Test
- Measurand: d_clearance [m]; tau_gap [s]; v_ego [m/s]
- Status: Draft
- Revision: 1.0
- Figures: F3, F4
- Related: ACC-SYS-PRF-001, ACC-SYS-FUN-005, ACC-SYS-FUN-021

### R12: Longitudinal dynamics limits (Document section)
Identifier block 020-039. Requirements in this sub-clause: ACC-SYS-PRF-020, ACC-SYS-PRF-021, ACC-SYS-PRF-022.
- Clause number: 6.2

#### ACC-SYS-PRF-020: Automatic deceleration limit (ACC System Requirement)
- Chapter: Performance
- Requirement text: While the ACC system is in the Active-Cruise state or the Active-Follow state, the ACC system shall limit the automatic deceleration of the subject vehicle to a 2 s moving average of not more than 3,5 m/s².
- EARS pattern: StateDriven
- Applicable states: Active-Cruise, Active-Follow
- Rationale: Engineering assumption, not a confirmed 2018 value. The limit lives in ISO 15622 cl. 6.4, Operational limits. The clause exists in the 2018 third edition and its title is confirmed from the publisher-hosted preview, but the preview truncates in cl. 6.2.3 and never reaches cl. 6.4, so the 2018 value could not be read from any primary source. The value of 3,5 m/s² over 2 s is verbatim from the 2010 second edition obtained through an unauthorised full-text copy and corroborated by two independent secondary summaries. The value is known to be volatile: the 1999 ISO/DIS set 3,0 m/s², relaxed to 3,5 m/s² by publication. This requirement therefore ships tagged UNVERIFIED-2018; obtaining ISO 15622:2018 cl. 6.4 and confirming the value is an open action in the assumptions register. Jerk is specified separately by ACC-SYS-PRF-021 because INCOSE R19 forbids combining the two. The transient authority ceiling that bounds this comfort limit is ACC-SYS-SAF-040.
- Source: ISO 15622:2010 cl. 6.4
- Verification tag: UNVERIFIED-2018
- Verification method: Test
- Measurand: a_x_ego [m/s^2]
- Status: Draft
- Revision: 1.0
- Figures: F4, F6
- Related: ACC-SYS-PRF-021, ACC-SYS-PRF-022, ACC-SYS-SAF-040

#### ACC-SYS-PRF-021: Automatic negative jerk limit (ACC System Requirement)
- Chapter: Performance
- Requirement text: While the ACC system is in the Active-Cruise state or the Active-Follow state, the ACC system shall limit the rate of increase of automatic deceleration of the subject vehicle to a 1 s moving average of not more than 2,5 m/s³.
- EARS pattern: StateDriven
- Applicable states: Active-Cruise, Active-Follow
- Rationale: Engineering assumption, not a confirmed 2018 value. The limit lives in ISO 15622 cl. 6.4, Operational limits, which exists in the 2018 third edition but is past the truncation point of the publisher-hosted preview. The value of 2,5 m/s³ averaged over 1 s is verbatim from the 2010 second edition via an unauthorised full-text copy and is identical in the 1999 ISO/DIS, which is the one clause-6.4 value that did not move between the draft and the published second edition; that stability raises confidence but does not make the 2018 value primary-verified. The requirement is therefore tagged UNVERIFIED-2018. Deceleration magnitude is specified separately by ACC-SYS-PRF-020 because INCOSE R19 forbids combining the two.
- Source: ISO 15622:2010 cl. 6.4; ISO/DIS 15622 (1999) cl. 6.4
- Verification tag: UNVERIFIED-2018
- Verification method: Test
- Measurand: a_x_ego [m/s^2]
- Status: Draft
- Revision: 1.0
- Figures: F4, F6
- Related: ACC-SYS-PRF-020, ACC-SYS-SAF-024

#### ACC-SYS-PRF-022: Automatic acceleration limit (ACC System Requirement)
- Chapter: Performance
- Requirement text: While the ACC system is in the Active-Cruise state or the Active-Follow state, the ACC system shall limit the automatic acceleration of the subject vehicle to not more than 2,0 m/s².
- EARS pattern: StateDriven
- Applicable states: Active-Cruise, Active-Follow
- Rationale: Engineering assumption, not a confirmed 2018 value. The limit lives in ISO 15622 cl. 6.4, Operational limits, which exists in the 2018 third edition but is past the truncation point of the publisher-hosted preview. The value a_max of not more than 2,0 m/s² is verbatim from the 2010 second edition via an unauthorised full-text copy and is identical in the 1999 ISO/DIS. The requirement is therefore tagged UNVERIFIED-2018. No averaging window is stated by either source, so the limit is written as an instantaneous bound, which is the conservative reading.
- Source: ISO 15622:2010 cl. 6.4; ISO/DIS 15622 (1999) cl. 6.4
- Verification tag: UNVERIFIED-2018
- Verification method: Test
- Measurand: a_x_ego [m/s^2]
- Status: Draft
- Revision: 1.0
- Figures: F6
- Related: ACC-SYS-PRF-020, ACC-SYS-PRF-042

### R13: Speed envelope (Document section)
Identifier block 040-059. Requirements in this sub-clause: ACC-SYS-PRF-040, ACC-SYS-PRF-041, ACC-SYS-PRF-042.
- Clause number: 6.3

#### ACC-SYS-PRF-040: Minimum selectable set speed (ACC System Requirement)
- Chapter: Performance
- Requirement text: The ACC system shall constrain the set speed to values of not less than 7 m/s.
- EARS pattern: Ubiquitous
- Applicable states: Standby, Active-Cruise, Active-Follow
- Rationale: Engineering assumption, not a confirmed 2018 value. ISO 15622 cl. 6.4 requires the minimum selectable set speed v_set_min to be not less than 7 m/s and not less than v_low. The clause exists in the 2018 third edition but is past the truncation point of the publisher-hosted preview; the value is verbatim from the 2010 second edition via an unauthorised full-text copy and identical in the 1999 ISO/DIS. Tagged UNVERIFIED-2018. The companion v_low floor of 5 m/s for automatic positive acceleration is deliberately not carried into a requirement, because the system is FSRA-type and the 2018 foreword confirms that automatic start from hold is no longer prohibited, so a 5 m/s floor on positive acceleration would contradict ACC-SYS-FUN-006. That omission is recorded in the assumptions register.
- Source: ISO 15622:2010 cl. 6.4; ISO/DIS 15622 (1999) cl. 6.4
- Verification tag: UNVERIFIED-2018
- Verification method: Test
- Measurand: v_set [m/s]
- Status: Draft
- Revision: 1.0
- Figures: F6
- Related: ACC-SYS-PRF-041, ACC-SYS-FUN-006

#### ACC-SYS-PRF-041: Maximum selectable set speed (ACC System Requirement)
- Chapter: Performance
- Requirement text: The ACC system shall constrain the set speed to values of not more than 180 km/h.
- EARS pattern: Ubiquitous
- Applicable states: Standby, Active-Cruise, Active-Follow
- Rationale: ISO 15622:2018 cl. 4 defines v_set_max as the maximum selectable set speed, confirmed from the publisher-hosted preview, but no retrieved edition of the standard sets a numeric ceiling, so the value is project-owned. 180 km/h is chosen as the ceiling because it covers the whole Euro NCAP Assisted Driving car-to-car test speed range, which reaches 130 km/h, with margin for unrestricted-motorway use, while remaining below the speed at which the forward-sensing range assumptions of ACC-SYS-PRF-003 would need re-derivation. Owned by the systems engineer, 2026-08-18.
- Source: ISO 15622:2018 cl. 4; PROJECT-CHOICE:systems-engineer
- Verification tag: DERIVED
- Verification method: Test
- Measurand: v_set [m/s]
- Status: Draft
- Revision: 1.0
- Figures: F6
- Related: ACC-SYS-PRF-040, ACC-SYS-PRF-003

#### ACC-SYS-PRF-042: Stop behind a gradually stopping target vehicle (ACC System Requirement)
- Chapter: Performance
- Requirement text: While the ACC system is in the Active-Follow state and the target vehicle speed is less than 10 m/s, when the target vehicle decelerates to standstill, the ACC system shall bring the subject vehicle to standstill behind the target vehicle.
- EARS pattern: Complex
- Applicable states: Active-Follow
- Rationale: ISO 15622:2018 cl. 6.2.3.1 states that from steady-state following an FSRA-type system will attempt to stop behind an already tracked and gradually stopping vehicle whose speed is below v_stopping, and gives v_stopping as 10 m/s; the value is read verbatim from the publisher-hosted 2018 preview. The standard phrases the capability with the future "will", which is a capability statement rather than a testable obligation, so the obligation is restated here with "shall" for an FSRA-type system, which is the classification of this system. The a_stopping deceleration value of the standard is past the truncation point of the preview and is therefore not carried into this requirement; the deceleration the system may use is bounded instead by ACC-SYS-PRF-020. The clearance at standstill is ACC-SYS-PRF-003 and the subsequent transition to Active-Hold is ACC-SYS-FUN-005.
- Source: ISO 15622:2018 cl. 6.2.3.1; ISO 15622:2018 cl. 7.3.2
- Verification tag: VERIFIED-PRIMARY
- Verification method: Test
- Measurand: v_ego [m/s]; v_target [m/s]; d_clearance [m]
- Status: Draft
- Revision: 1.0
- Figures: F4, F6
- Related: ACC-SYS-PRF-003, ACC-SYS-PRF-020, ACC-SYS-FUN-005

### R14: Scenario response performance (Document section)
Identifier block 060-079. Requirements in this sub-clause: ACC-SYS-PRF-060, ACC-SYS-PRF-061, ACC-SYS-PRF-062.
- Clause number: 6.4

#### ACC-SYS-PRF-060: Response to a braking target vehicle (ACC System Requirement)
- Chapter: Performance
- Requirement text: While the ACC system is in the Active-Follow state at a subject vehicle speed of 120 km/h, when the target vehicle decelerates at 4,0 m/s² to standstill, the ACC system shall maintain a clearance to the target vehicle of not less than 0,5 m.
- EARS pattern: Complex
- Applicable states: Active-Follow
- Rationale: The scenario is the Euro NCAP Assisted Driving car-to-car rear braking case, CCRb, with the lead vehicle braking at 4 m/s² at 100 % overlap; the deceleration value and the 120 km/h subject vehicle speed are read verbatim from Euro NCAP AD v2.2 (2024-09), which is the fixed scenario baseline of this project. Euro NCAP scores full avoidance rather than stating a minimum clearance, so the 0,5 m residual clearance is project-owned; it is chosen as a measurable no-contact criterion that a differential-GNSS test setup can resolve, and it is deliberately smaller than the 2,5 m steady-state floor of ACC-SYS-PRF-003 because this is a transient. The deceleration the system may use to achieve it is bounded by ACC-SYS-PRF-020 and ACC-SYS-SAF-040. Owned by the systems engineer, 2026-08-18.
- Source: Euro NCAP AD v2.2 (2024-09) §ACC car-to-car rear braking; PROJECT-CHOICE:systems-engineer
- Verification tag: DERIVED
- Verification method: Test
- Measurand: d_clearance [m]; a_x_ego [m/s^2]; v_ego [m/s]; v_target [m/s]
- Status: Draft
- Revision: 1.0
- Figures: F4
- Related: ACC-SYS-PRF-020, ACC-SYS-PRF-003, ACC-SYS-SAF-040

#### ACC-SYS-PRF-061: Response to a cut-out revealing a stationary vehicle (ACC System Requirement)
- Chapter: Performance
- Requirement text: When the target vehicle completes a lane change out of the subject vehicle lane at a time to collision of 3,00 s to a stationary vehicle ahead, the ACC system shall maintain a clearance to that stationary vehicle of not less than 0,5 m.
- EARS pattern: EventDriven
- Applicable states: Active-Follow, Active-Cruise
- Rationale: The scenario is the Euro NCAP Assisted Driving cut-out case: the lead vehicle performs a full lane change out of the lane of the vehicle under test with a 3,5 m lateral offset, revealing a stationary target, with the reference instant at a time to collision of 3,00 s. The geometry, the lateral offset and the 3,00 s reference instant are read verbatim from Euro NCAP AD v2.2 (2024-09); note that the current v1.1 (2025-10) protocol moves the collision-avoidance variant of this case to 2,00 s, so this requirement changes if the newer Vehicle Assistance protocol is adopted. As in ACC-SYS-PRF-060 the 0,5 m residual clearance is project-owned because Euro NCAP scores avoidance rather than a clearance. The latency of the target change itself is ACC-SYS-PRF-062. Owned by the systems engineer, 2026-08-18.
- Source: Euro NCAP AD v2.2 (2024-09) §ACC cut-out; PROJECT-CHOICE:systems-engineer
- Verification tag: DERIVED
- Verification method: Test
- Measurand: d_clearance [m]; a_x_ego [m/s^2]; v_ego [m/s]; target_id [enum]
- Status: Draft
- Revision: 1.0
- Figures: F5
- Related: ACC-SYS-PRF-062, ACC-SYS-FUN-023, ACC-SYS-SAF-041

#### ACC-SYS-PRF-062: Target reselection latency after a cut-out (ACC System Requirement)
- Chapter: Performance
- Requirement text: When the target vehicle completes a lane change out of the subject vehicle lane, the ACC system shall complete the selection of the target vehicle within 0,5 s of lane change completion.
- EARS pattern: EventDriven
- Applicable states: Active-Cruise, Active-Follow
- Rationale: ISO 15622:2018 cl. 6.1 requires automatic selection of the vehicle to be followed when more than one forward vehicle is present, and Euro NCAP AD v2.2 (2024-09) defines the cut-out geometry, but neither source sets a reselection latency, so the 0,5 s value is project-owned. It is chosen so that at the 90 km/h cut-out entry speed of the Euro NCAP case the subject vehicle travels not more than 12,5 m before the newly revealed vehicle is the target, which keeps the reselection inside the 3,00 s time to collision of ACC-SYS-PRF-061 with margin for the control response. This requirement carries the latency only; which vehicle is selected is ACC-SYS-FUN-023, so the selection rule is expressed once (INCOSE R32). Owned by the systems engineer, 2026-08-18.
- Source: ISO 15622:2018 cl. 6.1; Euro NCAP AD v2.2 (2024-09) §ACC cut-out; PROJECT-CHOICE:systems-engineer
- Verification tag: DERIVED
- Verification method: Test
- Measurand: target_id [enum]; t [s]; v_ego [m/s]
- Status: Draft
- Revision: 1.0
- Figures: F5
- Related: ACC-SYS-FUN-023, ACC-SYS-PRF-061

## R15: Safety and fault-handling requirements (Document section)
This clause carries 12 requirements with identifiers ACC-SYS-SAF-###, ordered by identifier and grouped into 4 sub-clauses that follow the identifier allocation blocks.
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- Clause number: 7

### R16: Fault detection and annunciation (Document section)
Identifier block 001-019. Requirements in this sub-clause: ACC-SYS-SAF-001, ACC-SYS-SAF-002, ACC-SYS-SAF-003, ACC-SYS-SAF-004.
- Clause number: 7.1

#### ACC-SYS-SAF-001: Detection of forward-sensing degradation (ACC System Requirement)
- Chapter: Safety-Fault-Handling
- Requirement text: If the ACC system detects that the forward-sensing field of view is obstructed or that the forward-sensing target data are implausible, then the ACC system shall set the forward-sensing health signal to the fault value within 300 ms of that detection.
- EARS pattern: UnwantedBehaviour
- Applicable states: Standby, Active-Cruise, Active-Follow, Active-Hold
- Rationale: ISO 15622:2018 cl. 6.6 is titled failure reactions but its content is past the truncation point of the publisher-hosted preview, so no standardised detection criterion or window is available. Both the criterion and the 300 ms window are project-owned: 300 ms is roughly six frames at the 20 Hz nominal forward-sensor rate, long enough to distinguish a persistent obstruction such as spray, ice or mud from a transient dropout, and short enough that the state transition of ACC-SYS-SAF-021 still completes inside the driver-reaction floor. This requirement sets the health signal only; the state transition it triggers is ACC-SYS-SAF-021 and the annunciation is ACC-SYS-SAF-004, kept separate because INCOSE R19 forbids combining a detection, a transition and an output. Owned by the systems engineer, 2026-08-18.
- Source: ISO 15622:2018 cl. 6.6; PROJECT-CHOICE:systems-engineer
- Verification tag: DERIVED
- Verification method: Test
- Measurand: sensor_health [enum]; target_detected [bool]; t [s]
- Status: Draft
- Revision: 1.0
- Figures: F1
- Related: ACC-SYS-SAF-021, ACC-SYS-SAF-004

#### ACC-SYS-SAF-002: Detection of stale vehicle bus signals (ACC System Requirement)
- Chapter: Safety-Fault-Handling
- Requirement text: If the ACC system detects that a vehicle bus signal used for longitudinal control has not been updated for more than 200 ms, then the ACC system shall set the vehicle bus health signal to the stale value within 100 ms of that detection.
- EARS pattern: UnwantedBehaviour
- Applicable states: Standby, Active-Cruise, Active-Follow, Active-Hold
- Rationale: No retrieved clause of ISO 15622:2018 addresses vehicle bus signal timeouts; cl. 6.6 failure reactions is past the truncation point of the publisher-hosted preview. Both windows are project-owned. 200 ms is chosen as four periods of the 50 ms nominal wheel-speed and yaw-rate transmission cycle shown crossing the system boundary in figure F1, which tolerates isolated frame loss without tolerating a silent sender; 100 ms keeps the health signal ahead of the 200 ms state transition of ACC-SYS-SAF-022. Owned by the systems engineer, 2026-08-18.
- Source: PROJECT-CHOICE:systems-engineer
- Verification tag: DERIVED
- Verification method: Test
- Measurand: bus_health [enum]; v_ego [m/s]; t [s]
- Status: Draft
- Revision: 1.0
- Figures: F1
- Related: ACC-SYS-SAF-022, ACC-SYS-SAF-004

#### ACC-SYS-SAF-003: Detection of loss of actuation authority (ACC System Requirement)
- Chapter: Safety-Fault-Handling
- Requirement text: If the ACC system detects that the longitudinal acceleration of the subject vehicle differs from the commanded longitudinal acceleration by more than 1,0 m/s² for more than 500 ms, then the ACC system shall set the actuation health signal to the fault value within 200 ms of that detection.
- EARS pattern: UnwantedBehaviour
- Applicable states: Active-Cruise, Active-Follow, Active-Hold
- Rationale: Loss of brake or powertrain actuation authority is a cl. 6.6 failure reaction concern, and cl. 6.6 is past the truncation point of the publisher-hosted preview, so the detection criterion is project-owned. The criterion is written as a plant-response mismatch rather than as an actuator-internal diagnostic so that it stays free of design and implementation, as ASPICE SYS.2.BP1 note 02 requires. 1,0 m/s² is chosen to sit above the road-gradient and load disturbances that a longitudinal controller absorbs and below the 2,0 m/s² acceleration limit of ACC-SYS-PRF-022, so a full loss of authority is detected while normal tracking error is not. 500 ms is chosen to exceed the actuator response time that the deceleration ramp of ACC-SYS-PRF-021 already implies. Overlap rule O1 places loss of the ability to meet a limit in the Safety chapter. Owned by the systems engineer, 2026-08-18.
- Source: ISO 15622:2018 cl. 6.6; PROJECT-CHOICE:systems-engineer
- Verification tag: DERIVED
- Verification method: Test
- Measurand: actuation_health [enum]; a_x_ego [m/s^2]; a_x_cmd_acc [m/s^2]; t [s]
- Status: Draft
- Revision: 1.0
- Figures: F1
- Related: ACC-SYS-SAF-022, ACC-SYS-PRF-022

#### ACC-SYS-SAF-004: Annunciation of a fault to the driver (ACC System Requirement)
- Chapter: Safety-Fault-Handling
- Requirement text: When the ACC system enters the Degraded-Fault state, the ACC system shall present to the driver a fault indication that differs from the indication of the ACC state within 500 ms of entering that state.
- EARS pattern: EventDriven
- Applicable states: Degraded-Fault
- Rationale: ISO 15622:2018 cl. 6.3 covers the driver interface and cl. 6.6 covers failure reactions; both are past the truncation point of the publisher-hosted preview, so the annunciation form and timing are project-owned. 500 ms is chosen to be well inside the driver-reaction floor of roughly 250 ms plus a glance transition, so the indication is present before the driver can react to the vehicle behaviour that prompted it. The requirement that the fault indication be distinguishable from the nominal state indication of ACC-SYS-FUN-060 is the point of the requirement, and follows overlap rule O4, which assigns driver-facing warning of degraded capability to the Safety chapter. Owned by the systems engineer, 2026-08-18.
- Source: ISO 15622:2018 cl. 6.3; ISO 15622:2018 cl. 6.6; PROJECT-CHOICE:systems-engineer
- Verification tag: DERIVED
- Verification method: Demonstration
- Status: Draft
- Revision: 1.0
- Figures: F1, F2
- Related: ACC-SYS-FUN-060, ACC-SYS-SAF-021

### R17: Degraded-state behaviour and fault transitions (Document section)
Identifier block 020-039. Requirements in this sub-clause: ACC-SYS-SAF-021, ACC-SYS-SAF-022, ACC-SYS-SAF-023, ACC-SYS-SAF-024.
- Clause number: 7.2

#### ACC-SYS-SAF-021: Transition to Degraded-Fault on loss of forward sensing (ACC System Requirement)
- Chapter: Safety-Fault-Handling
- Requirement text: If the ACC system detects that the forward-sensing function has been unavailable for more than 500 ms while the ACC system is in the Active-Cruise state, the Active-Follow state or the Active-Hold state, then the ACC system shall enter the Degraded-Fault state within 200 ms of that detection.
- EARS pattern: UnwantedBehaviour
- Applicable states: Active-Cruise, Active-Follow, Active-Hold, Degraded-Fault
- Rationale: ISO 15622:2018 cl. 6.6 is titled failure reactions but its content is past the truncation point of the publisher-hosted preview, so no standardised detection window or transition latency is available. Both numbers are project-owned: 500 ms is chosen as roughly two forward-sensor frames at a 20 Hz nominal rate, long enough to reject a single dropped frame and short enough that at 30 m/s the subject vehicle travels 15 m unsensed; 200 ms is chosen to be below the driver-reaction floor of roughly 250 ms so the state change precedes any driver response. Owned by the systems engineer, 2026-08-18. Annunciation to the driver is a separate requirement (ACC-SYS-SAF-004) because INCOSE R19 forbids combining a state transition with an output.
- Source: PROJECT-CHOICE:systems-engineer
- Verification tag: DERIVED
- Verification method: Test
- Measurand: sensor_health [enum]; acc_state [enum]; t [s]
- Status: Draft
- Revision: 1.0
- Figures: F1, F2
- Related: ACC-SYS-SAF-022, ACC-SYS-FUN-001

#### ACC-SYS-SAF-022: Transition to Degraded-Fault on bus or actuation fault (ACC System Requirement)
- Chapter: Safety-Fault-Handling
- Requirement text: If the vehicle bus health signal or the actuation health signal indicates a fault while the ACC system is in the Active-Cruise state, the Active-Follow state or the Active-Hold state, then the ACC system shall enter the Degraded-Fault state within 200 ms of that indication.
- EARS pattern: UnwantedBehaviour
- Applicable states: Active-Cruise, Active-Follow, Active-Hold, Degraded-Fault
- Rationale: Companion to ACC-SYS-SAF-021 for the two fault sources that do not come from forward sensing: the vehicle bus health signal set by ACC-SYS-SAF-002 and the actuation health signal set by ACC-SYS-SAF-003. The trigger sets of the two requirements are disjoint, so the transition is expressed once for each source class and no requirement is duplicated (INCOSE R32). The 200 ms transition latency is the same project-owned value as in ACC-SYS-SAF-021 and is chosen for the same reason, to precede the driver-reaction floor. Owned by the systems engineer, 2026-08-18.
- Source: DERIVED-FROM:ACC-SYS-SAF-021; PROJECT-CHOICE:systems-engineer
- Verification tag: DERIVED
- Verification method: Test
- Measurand: bus_health [enum]; actuation_health [enum]; acc_state [enum]; t [s]
- Status: Draft
- Revision: 1.0
- Figures: F2
- Related: ACC-SYS-SAF-002, ACC-SYS-SAF-003, ACC-SYS-SAF-021

#### ACC-SYS-SAF-023: Exit from Degraded-Fault to Standby (ACC System Requirement)
- Chapter: Safety-Fault-Handling
- Requirement text: If the forward-sensing health signal, the vehicle bus health signal and the actuation health signal indicate no fault while the ACC system is in the Degraded-Fault state, then the ACC system shall enter the Standby state within 500 ms of that indication.
- EARS pattern: UnwantedBehaviour
- Applicable states: Degraded-Fault, Standby
- Rationale: Without this requirement the Degraded-Fault state is a sink from which only an ignition cycle escapes, which would make a recovered transient fault permanently disabling. Recovery to Standby rather than directly to an active state is deliberate: it forces a fresh driver set command through ACC-SYS-FUN-004 so control never resumes without driver intent. No retrieved clause of ISO 15622:2018 specifies the recovery path, so both the path and the 500 ms latency are project-owned; 500 ms is the same order as the annunciation latency of ACC-SYS-SAF-004 so the driver sees the fault indication clear at the same time as the state changes. Owned by the systems engineer, 2026-08-18.
- Source: PROJECT-CHOICE:systems-engineer
- Verification tag: DERIVED
- Verification method: Test
- Measurand: sensor_health [enum]; bus_health [enum]; actuation_health [enum]; acc_state [enum]
- Status: Draft
- Revision: 1.0
- Figures: F2
- Related: ACC-SYS-SAF-021, ACC-SYS-SAF-022, ACC-SYS-FUN-004

#### ACC-SYS-SAF-024: Bounded release of automatic brake force (ACC System Requirement)
- Chapter: Safety-Fault-Handling
- Requirement text: If the ACC system ends automatic brake control while the subject vehicle is decelerating, then the ACC system shall reduce the commanded deceleration at a rate of not more than 2,5 m/s³.
- EARS pattern: UnwantedBehaviour
- Applicable states: Active-Cruise, Active-Follow, Active-Hold, Degraded-Fault, Standby
- Rationale: Engineering assumption, not a confirmed 2018 value. ISO 15622 cl. 6.4, Operational limits, carries a qualitative requirement that brake force is not released suddenly on automatic deactivation; the clause exists in the 2018 third edition but is past the truncation point of the publisher-hosted preview, so the 2018 wording could not be read. The qualitative requirement is verbatim from the 2010 second edition via an unauthorised full-text copy and is present in the 1999 ISO/DIS. Because that source states no rate, the bound reuses the 2,5 m/s³ jerk value of the same clause, which ACC-SYS-PRF-021 already applies to increasing deceleration, so release and application are bounded symmetrically; the value therefore inherits the UNVERIFIED-2018 tag of its source clause. This requirement governs every exit from automatic braking, including the transitions of ACC-SYS-FUN-003, ACC-SYS-FUN-042 and ACC-SYS-SAF-021.
- Source: ISO 15622:2010 cl. 6.4; DERIVED-FROM:ACC-SYS-PRF-021
- Verification tag: UNVERIFIED-2018
- Verification method: Test
- Measurand: a_x_cmd_acc [m/s^2]; a_x_ego [m/s^2]; t [s]
- Status: Draft
- Revision: 1.0
- Figures: F4
- Related: ACC-SYS-PRF-021, ACC-SYS-FUN-042, ACC-SYS-FUN-003

### R18: Authority limits and interaction with other systems (Document section)
Identifier block 040-059. Requirements in this sub-clause: ACC-SYS-SAF-040, ACC-SYS-SAF-041, ACC-SYS-SAF-042.
- Clause number: 7.3

#### ACC-SYS-SAF-040: Deceleration authority ceiling (ACC System Requirement)
- Chapter: Safety-Fault-Handling
- Requirement text: The ACC system shall limit the instantaneous deceleration it commands of the subject vehicle to not more than 5,0 m/s².
- EARS pattern: Ubiquitous
- Applicable states: Active-Cruise, Active-Follow, Active-Hold
- Rationale: This is an authority boundary, not a comfort limit: it separates the braking domain of ACC from autonomous emergency braking, which shares the brake actuator (see figure F1). The Assisted Driving protocol of Euro NCAP v2.2 (2024-09) draws the assessment demarcation where braking levels stay below approximately 5 m/s², read verbatim from the official protocol. That statement is an assessment demarcation rather than a design limit, so the project converts it into a hard commanded-deceleration ceiling and owns the conversion; the word approximately is removed because INCOSE R7 forbids vague terms in a requirement statement. Placed in the Safety chapter rather than Performance under overlap rule O6, because its purpose is inter-system arbitration. The 2 s-average comfort limit of 3,5 m/s² (ACC-SYS-PRF-020) is the tighter nominal constraint; this requirement bounds the transient. Owned by the systems engineer, 2026-08-18.
- Source: Euro NCAP AD v2.2 (2024-09) §ACC-vs-AEB demarcation; PROJECT-CHOICE:systems-engineer
- Verification tag: DERIVED
- Verification method: Test
- Measurand: a_x_cmd_acc [m/s^2]
- Status: Draft
- Revision: 1.0
- Figures: F1, F6
- Related: ACC-SYS-PRF-020, ACC-SYS-SAF-041

#### ACC-SYS-SAF-041: Yielding brake authority to autonomous emergency braking (ACC System Requirement)
- Chapter: Safety-Fault-Handling
- Requirement text: If the autonomous emergency braking system requests brake actuation, then the ACC system shall limit the deceleration it commands to 0,0 m/s² until that request ends.
- EARS pattern: UnwantedBehaviour
- Applicable states: Active-Cruise, Active-Follow, Active-Hold
- Rationale: ACC and autonomous emergency braking share one brake actuator, shown crossing the system boundary in figure F1, so the arbitration between them has to be specified somewhere and this artifact is the system-layer document that owns the ACC side of it. The Assisted Driving protocol of Euro NCAP v2.2 (2024-09) assesses ACC capability only where it is confirmed that autonomous emergency braking did not intervene, which establishes that the two functions are expected to be separable but sets no arbitration rule, so the rule is project-owned. Yielding completely rather than adding requests is chosen because summed requests would make the achieved deceleration depend on the internal state of two systems and would defeat the ceiling of ACC-SYS-SAF-040. Owned by the systems engineer, 2026-08-18.
- Source: Euro NCAP AD v2.2 (2024-09) §ACC-vs-AEB demarcation; PROJECT-CHOICE:systems-engineer
- Verification tag: DERIVED
- Verification method: Test
- Measurand: aeb_brake_request [bool]; a_x_cmd_acc [m/s^2]
- Status: Draft
- Revision: 1.0
- Figures: F1, F6
- Related: ACC-SYS-SAF-040, ACC-SYS-PRF-060

#### ACC-SYS-SAF-042: Inhibit of activation while a fault is present (ACC System Requirement)
- Chapter: Safety-Fault-Handling
- Requirement text: If the driver operates the set switch while the ACC system is in the Degraded-Fault state, then the ACC system shall remain in the Degraded-Fault state.
- EARS pattern: UnwantedBehaviour
- Applicable states: Degraded-Fault
- Rationale: ACC-SYS-FUN-004 activates the system on a driver set command from the Standby state; this requirement closes the corresponding path from the Degraded-Fault state so that a driver cannot activate longitudinal control while the system knows it cannot deliver it. Written as an unwanted-behaviour statement with a positive response, remaining in the current state, rather than as a prohibition, because INCOSE R17 discourages using "not" as the verb qualifier. No retrieved clause of ISO 15622:2018 states an activation inhibit for the fault case, so the requirement is project-owned; the LSRA activation inhibit below v_low in cl. 6.1 is the closest analogue and does not apply to an FSRA-type system. Owned by the systems engineer, 2026-08-18.
- Source: PROJECT-CHOICE:systems-engineer
- Verification tag: DERIVED
- Verification method: Test
- Measurand: set_switch [bool]; acc_state [enum]
- Status: Draft
- Revision: 1.0
- Figures: F2
- Related: ACC-SYS-FUN-004, ACC-SYS-SAF-023

### R19: Driver availability and takeover (Document section)
Identifier block 060-079. Requirements in this sub-clause: ACC-SYS-SAF-060.
- Clause number: 7.4

#### ACC-SYS-SAF-060: Driver availability escalation before resume (ACC System Requirement)
- Chapter: Safety-Fault-Handling
- Requirement text: If the ACC system detects that the driver hands-off condition is present while the ACC system is in the Active-Hold state, then the ACC system shall begin the takeover warning escalation before the subject vehicle speed reaches 10 km/h.
- EARS pattern: UnwantedBehaviour
- Applicable states: Active-Hold, Degraded-Fault
- Rationale: The Assisted Driving protocol of Euro NCAP v2.2 (2024-09) states in the ACC auto-resume scenario that on resuming, the hands-off warning escalation must begin before the vehicle under test reaches 10 km/h; the threshold is read verbatim from the official protocol, hence VERIFIED-PRIMARY. The requirement is placed in the Safety chapter under overlap rule O4 because it is a driver-facing warning of a required takeover rather than an indication of nominal state. It complements ACC-SYS-FUN-006, which specifies the driver resume command itself, and it bounds any implementation that resumes from hold without a driver command, which the 2018 foreword of ISO 15622 permits.
- Source: Euro NCAP AD v2.2 (2024-09) §ACC Auto-Resume
- Verification tag: VERIFIED-PRIMARY
- Verification method: Test
- Measurand: hands_off [bool]; v_ego [m/s]; acc_state [enum]
- Status: Draft
- Revision: 1.0
- Figures: F2
- Related: ACC-SYS-FUN-006, ACC-SYS-SAF-004
